EtsiTs102941TypesCaManagement
  { itu-t(0) identified-organization(4) etsi(0) itsDomain(5) wg5(5) ts(102941) caManagement(8) version1(1)}

DEFINITIONS AUTOMATIC TAGS ::=
BEGIN

IMPORTS

EtsiTs103097Certificate, EtsiTs103097Data-Signed 
FROM	
EtsiTs103097Module 
{itu-t(0) identified-organization(4) etsi(0) itsDomain(5) wg5(5) ts(103097) securedMessageV1(0)}

PublicKeys, CertificateSubjectAttributes
FROM EtsiTs102941BaseTypes
{ itu-t(0) identified-organization(4) etsi(0) itsDomain(5) wg5(5) ts(102941) baseTypes(3) version1(1)}

;

/************
-- CA certificate request 
************/

CaCertificateRequest ::= SEQUENCE {
  publicKeys                  PublicKeys,
  requestedSubjectAttributes  CertificateSubjectAttributes,
  ...	 
}

END
